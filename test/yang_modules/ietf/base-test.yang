module base-test {
    yang-version "1";
    namespace "http://rob.sh/yang/test/base-test";
    prefix "foo";

    import ietf-yang-schema-mount {
        prefix yangmnt;
    }

    description
        "A test module that checks that the plugin works OK";

    revision 2014-01-01 {
        description "april-fools";
        reference "fooled-you";
    }

    container int-container {
        description
            "A container";

        leaf eight {
            type int8;
            description
              "A test leaf for uint8";
        }

        yangmnt:mount-point "root" {
            description "mount point for testing";
        }
    }
}
